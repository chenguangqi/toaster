module toaster {
    yang-version 1;
    namespace "urn:cgq:params:xml:ns:yang:toaster";
    prefix "toaster";

    organization "Netconf Central";
    contact "Andy Bierman <andy@netconfcentral.org>";
    description "YANG version of the TOASTER-MIB.";

    revision "2017-05-10" {
        description "Initial revision of toaster model";
    }

    // declares a base identity, in this case a base type for different types of toast.
    identity toast-type {
        description "Base for all bread types supported by the toaster. New bread types not listed here may be added in the future.";
    }

    // the below identity section is used to define globally unique identities.
    // Note - removed a number of different types of bread to shorten the text length.
    identity white-bread {
        base toaster:toast-type;       // logically extending the declared toast-type above.
        description "White bread.";  // free text description of this type.
    }

    identity wheat-bread {
        base toaster:toast-type;
        description "Wheat bread";
    }

    // defines a new "Type" string type which limits the length
    typedef DisplayString {
        type string {
            //length "0 .. 255";
        }
        description "YANG version of the SMIv2 DisplayString TEXTUAL-CONVENTION.";
        reference "RFC 2579, section 2.";
    }

    // This definition is the top-level configuration "item" that defines a toaster. The "presence" flag
    // connotes there can only be one instance of a toaster which, if present, indicates the service is available.
    container toaster {
        presence "Indicates the toaster service is available";
        description "Top-level container for all toaster database objects.";

        // Note in these three attributes that config = false. This indicates that they are operational attributes.
        leaf toasterManufacturer {
            type DisplayString;
            config false;
            mandatory true;
            description "The name of the toaster's manufacturer. For instance, Microsoft Toaster.";
        }

        leaf toasterModelNumber {
            type DisplayString;
            config false;
            mandatory true;
            description "The name of the toaster's model. For instance, Radiant Automatic.";
        }

        leaf toasterStatus {
            type enumeration {
                enum "up" {
                    value 1;
                    description "The toaster knob position is up. No toast is being made now.";
                }
                enum "down" {
                    value 2;
                    description "The toaster knob position is down. Toast is being made now.";
                }
            }
            config false;
            mandatory true;
            description "This variable indicates the current state of the toaster.";
        }
    }
}
