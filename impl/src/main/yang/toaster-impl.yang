module toaster-impl {
    yang-version 1;
    namespace "urn:cgq:params:xml:ns:yang:toaster:impl";
    prefix "toaster-impl";

    import config { prefix config; revision-date 2013-04-05; }
    import opendaylight-md-sal-binding { prefix md-sal-binding; revision-date 2013-10-28;}

    description
        "Service definition for toaster project";

    revision "2017-05-10" {
        description
            "Initial revision";
    }

    identity toaster {
        base config:module-type;
        config:java-name-prefix Toaster;
    }

    augment "/config:modules/config:module/config:configuration" {
        case toaster {
            when "/config:modules/config:module/config:type = 'toaster'";
            container broker {
                uses config:service-ref {
                    refine type {
                        mandatory true;
                        config:required-identity md-sal-binding:binding-broker-osgi-registry;
                    }
                }
            }
        }
    }
}
